Option Explicit
'Script written by <insert name>
'Script copyrighted by <insert company name>
'Script version 12 July 2023 10:56:44

Call Main()
Sub Main()
	Dim desNo, fileNames, filePathName, iterations
	Dim designNames:designNames = array("A01R00100.igs", "A01R00101.igs", "A01R00102.igs", "A01R00103.igs", "A01R00104.igs", "A01R00105.igs", "A01R00106.igs", "A01R00107.igs", "A01R00108.igs", "A01R00109.igs", "A01R00110.igs", "A01R00111.igs", "A01R00112.igs", "A01R00113.igs", "A01R00114.igs", "A01R00115.igs", "A01R00116.igs", "A01R00117.igs", "A01R00118.igs", "A01R00119.igs", "A01R00120.igs", "A01R00121.igs", "A01R00122.igs", "A01R00123.igs", "A01R00124.igs", "A01R00300.igs", "A01R00301.igs", "A01R00302.igs", "A01R00303.igs", "A01R00304.igs", "A01R00305.igs", "A01R00306.igs", "A01R00307.igs", "A01R00308.igs", "A01R00309.igs", "A01R00310.igs", "A01R00311.igs", "A01R00312.igs", "A01R00313.igs", "A01R00314.igs", "A01R00315.igs", "A01R00316.igs", "A01R00317.igs", "A01R00318.igs", "A01R00319.igs", "A01R00320.igs", "A01R00321.igs", "A01R00322.igs", "A01R00323.igs", "A01R00324.igs", "A01R00500.igs", "A01R00501.igs", "A01R00502.igs", "A01R00503.igs", "A01R00504.igs", "A01R00505.igs", "A01R00506.igs", "A01R00507.igs", "A01R00508.igs", "A01R00509.igs", "A01R00510.igs", "A01R00511.igs", "A01R00512.igs", "A01R00513.igs", "A01R00514.igs", "A01R00515.igs", "A01R00516.igs", "A01R00517.igs", "A01R00518.igs", "A01R00519.igs", "A01R00520.igs", "A01R00521.igs", "A01R00522.igs", "A01R00523.igs", "A01R00524.igs", "A01R00700.igs", "A01R00701.igs", "A01R00702.igs", "A01R00703.igs", "A01R00704.igs", "A01R00705.igs", "A01R00706.igs", "A01R00707.igs", "A01R00708.igs", "A01R00709.igs", "A01R00710.igs", "A01R00711.igs", "A01R00712.igs", "A01R00713.igs", "A01R00714.igs", "A01R00715.igs", "A01R00716.igs", "A01R00717.igs", "A01R00718.igs", "A01R00719.igs", "A01R00720.igs", "A01R00721.igs", "A01R00722.igs", "A01R00723.igs", "A01R00724.igs", "A01R00900.igs", "A01R00901.igs", "A01R00902.igs", "A01R00903.igs", "A01R00904.igs", "A01R00905.igs", "A01R00906.igs", "A01R00907.igs", "A01R00908.igs", "A01R00909.igs", "A01R00910.igs", "A01R00911.igs", "A01R00912.igs", "A01R00913.igs", "A01R00914.igs", "A01R00915.igs", "A01R00916.igs", "A01R00917.igs", "A01R00918.igs", "A01R00919.igs", "A01R00921.igs", "A01R00922.igs", "A01R00923.igs", "A01R00924.igs", "A01R01100.igs", "A01R01101.igs", "A01R01102.igs", "A01R01103.igs", "A01R01104.igs", "A01R01105.igs", "A01R01106.igs", "A01R01107.igs", "A01R01108.igs", "A01R01109.igs", "A01R01110.igs", "A01R01111.igs", "A01R01112.igs", "A01R01113.igs", "A01R01114.igs", "A01R01115.igs", "A01R01116.igs", "A01R01118.igs", "A01R01119.igs", "A01R01120.igs", "A01R01121.igs", "A01R01122.igs", "A01R01123.igs", "A01R01124.igs", "A01R01300.igs", "A01R01301.igs", "A01R01302.igs", "A01R01303.igs", "A01R01304.igs", "A01R01305.igs", "A01R01306.igs", "A01R01307.igs", "A01R01308.igs", "A01R01309.igs", "A01R01310.igs", "A01R01312.igs", "A01R01313.igs", "A01R01314.igs", "A01R01315.igs", "A01R01316.igs", "A01R01317.igs", "A01R01318.igs", "A01R01319.igs", "A01R01320.igs", "A01R01321.igs", "A01R01322.igs", "A01R01323.igs", "A01R01324.igs", "A01R01500.igs", "A01R01501.igs", "A01R01502.igs", "A01R01503.igs", "A01R01504.igs", "A01R01505.igs", "A01R01506.igs", "A01R01507.igs", "A01R01508.igs", "A01R01509.igs", "A01R01510.igs", "A01R01511.igs", "A01R01512.igs", "A01R01513.igs", "A01R01514.igs", "A01R01515.igs", "A01R01516.igs", "A01R01517.igs", "A01R01518.igs", "A01R01519.igs", "A01R01520.igs", "A01R01521.igs", "A01R01522.igs", "A01R01523.igs", "A01R01524.igs", "A01R01700.igs", "A01R01701.igs", "A01R01702.igs", "A01R01703.igs", "A01R01704.igs", "A01R01705.igs", "A01R01706.igs", "A01R01707.igs", "A01R01708.igs", "A01R01709.igs", "A01R01710.igs", "A01R01711.igs", "A01R01712.igs", "A01R01713.igs", "A01R01714.igs", "A01R01715.igs", "A01R01716.igs", "A01R01718.igs", "A01R01719.igs", "A01R01720.igs", "A01R01721.igs", "A01R01722.igs", "A01R01723.igs", "A01R01724.igs", "A01R01900.igs", "A01R01901.igs", "A01R01902.igs", "A01R01903.igs", "A01R01904.igs", "A01R01905.igs", "A01R01906.igs", "A01R01907.igs", "A01R01908.igs", "A01R01909.igs", "A01R01910.igs", "A01R01911.igs", "A01R01912.igs", "A01R01913.igs", "A01R01914.igs", "A01R01915.igs", "A01R01916.igs", "A01R01917.igs", "A01R01918.igs", "A01R01919.igs", "A01R01920.igs", "A01R01921.igs", "A01R01922.igs", "A01R01923.igs", "A01R01924.igs", "A01R02100.igs", "A01R02102.igs", "A01R02103.igs", "A01R02104.igs", "A01R02106.igs", "A01R02107.igs", "A01R02108.igs", "A01R02109.igs", "A01R02110.igs", "A01R02111.igs", "A01R02112.igs", "A01R02113.igs", "A01R02114.igs", "A01R02115.igs", "A01R02116.igs", "A01R02117.igs", "A01R02118.igs", "A01R02119.igs", "A01R02120.igs", "A01R02121.igs", "A01R02122.igs", "A01R02123.igs", "A01R02124.igs", "A01R02300.igs", "A01R02301.igs", "A01R02302.igs", "A01R02303.igs", "A01R02304.igs", "A01R02305.igs", "A01R02306.igs", "A01R02307.igs", "A01R02308.igs", "A01R02309.igs", "A01R02310.igs", "A01R02311.igs", "A01R02312.igs", "A01R02313.igs", "A01R02314.igs", "A01R02315.igs", "A01R02316.igs", "A01R02317.igs", "A01R02318.igs", "A01R02319.igs", "A01R02320.igs", "A01R02321.igs", "A01R02322.igs", "A01R02323.igs", "A01R02324.igs", "A01R02500.igs", "A01R02501.igs", "A01R02502.igs", "A01R02503.igs", "A01R02504.igs", "A01R02505.igs", "A01R02506.igs", "A01R02507.igs", "A01R02508.igs", "A01R02509.igs", "A01R02510.igs", "A01R02511.igs", "A01R02512.igs", "A01R02513.igs", "A01R02514.igs", "A01R02515.igs", "A01R02516.igs", "A01R02517.igs", "A01R02518.igs", "A01R02519.igs", "A01R02520.igs", "A01R02521.igs", "A01R02522.igs", "A01R02523.igs", "A01R02524.igs", "A01R02700.igs", "A01R02701.igs", "A01R02702.igs", "A01R02703.igs", "A01R02704.igs", "A01R02705.igs", "A01R02706.igs", "A01R02707.igs", "A01R02708.igs", "A01R02709.igs", "A01R02710.igs", "A01R02711.igs", "A01R02712.igs", "A01R02713.igs", "A01R02714.igs", "A01R02715.igs", "A01R02716.igs", "A01R02717.igs", "A01R02718.igs", "A01R02719.igs", "A01R02720.igs", "A01R02721.igs", "A01R02722.igs", "A01R02723.igs", "A01R02724.igs", "A01R02900.igs", "A01R02901.igs", "A01R02902.igs", "A01R02903.igs", "A01R02904.igs", "A01R02905.igs", "A01R02906.igs", "A01R02907.igs", "A01R02908.igs", "A01R02909.igs", "A01R02910.igs", "A01R02911.igs", "A01R02912.igs", "A01R02913.igs", "A01R02914.igs", "A01R02915.igs", "A01R02916.igs", "A01R02917.igs", "A01R02918.igs", "A01R02919.igs", "A01R02920.igs", "A01R02921.igs", "A01R02922.igs", "A01R02923.igs", "A01R02924.igs", "A01R03100.igs", "A01R03101.igs", "A01R03102.igs", "A01R03103.igs", "A01R03104.igs", "A01R03105.igs", "A01R03106.igs", "A01R03107.igs", "A01R03108.igs", "A01R03109.igs", "A01R03110.igs", "A01R03111.igs", "A01R03112.igs", "A01R03113.igs", "A01R03114.igs", "A01R03115.igs", "A01R03116.igs", "A01R03117.igs", "A01R03118.igs", "A01R03119.igs", "A01R03120.igs", "A01R03121.igs", "A01R03122.igs", "A01R03123.igs", "A01R03124.igs", "A01R03300.igs", "A01R03301.igs", "A01R03302.igs", "A01R03303.igs", "A01R03304.igs", "A01R03305.igs", "A01R03306.igs", "A01R03307.igs", "A01R03308.igs", "A01R03309.igs", "A01R03310.igs", "A01R03311.igs", "A01R03313.igs", "A01R03314.igs", "A01R03315.igs", "A01R03316.igs", "A01R03317.igs", "A01R03318.igs", "A01R03319.igs", "A01R03320.igs", "A01R03321.igs", "A01R03322.igs", "A01R03323.igs", "A01R03324.igs", "A01R03500.igs", "A01R03501.igs", "A01R03502.igs", "A01R03503.igs", "A01R03504.igs", "A01R03505.igs", "A01R03506.igs", "A01R03507.igs", "A01R03508.igs", "A01R03509.igs", "A01R03510.igs", "A01R03511.igs", "A01R03512.igs", "A01R03513.igs", "A01R03514.igs", "A01R03515.igs", "A01R03516.igs", "A01R03517.igs", "A01R03518.igs", "A01R03519.igs", "A01R03520.igs", "A01R03521.igs", "A01R03522.igs", "A01R03523.igs", "A01R03524.igs", "A01R03700.igs", "A01R03701.igs", "A01R03702.igs", "A01R03703.igs", "A01R03704.igs", "A01R03705.igs", "A01R03706.igs", "A01R03707.igs", "A01R03708.igs", "A01R03709.igs", "A01R03710.igs", "A01R03711.igs", "A01R03712.igs", "A01R03713.igs", "A01R03714.igs", "A01R03715.igs", "A01R03716.igs", "A01R03717.igs", "A01R03718.igs", "A01R03720.igs", "A01R03721.igs", "A01R03722.igs", "A01R03723.igs", "A01R03724.igs", "A01R03900.igs", "A01R03901.igs", "A01R03902.igs", "A01R03903.igs", "A01R03904.igs", "A01R03905.igs", "A01R03906.igs", "A01R03907.igs", "A01R03908.igs", "A01R03909.igs", "A01R03910.igs", "A01R03911.igs", "A01R03912.igs", "A01R03913.igs", "A01R03914.igs", "A01R03915.igs", "A01R03916.igs", "A01R03917.igs", "A01R03918.igs", "A01R03919.igs", "A01R03920.igs", "A01R03921.igs", "A01R03922.igs", "A01R03923.igs", "A01R03924.igs", "A01R04100.igs", "A01R04101.igs", "A01R04102.igs", "A01R04103.igs", "A01R04104.igs", "A01R04105.igs", "A01R04106.igs", "A01R04107.igs", "A01R04108.igs", "A01R04109.igs", "A01R04110.igs", "A01R04111.igs", "A01R04112.igs", "A01R04113.igs", "A01R04114.igs", "A01R04115.igs", "A01R04116.igs", "A01R04117.igs", "A01R04118.igs", "A01R04119.igs", "A01R04121.igs", "A01R04122.igs", "A01R04123.igs", "A01R04124.igs", "A01R04300.igs", "A01R04301.igs", "A01R04302.igs", "A01R04303.igs", "A01R04304.igs", "A01R04305.igs", "A01R04306.igs", "A01R04307.igs", "A01R04308.igs", "A01R04309.igs", "A01R04310.igs", "A01R04311.igs", "A01R04312.igs", "A01R04313.igs", "A01R04314.igs", "A01R04315.igs", "A01R04316.igs", "A01R04317.igs", "A01R04318.igs", "A01R04319.igs", "A01R04320.igs", "A01R04321.igs", "A01R04322.igs", "A01R04323.igs", "A01R04324.igs", "A01R04500.igs", "A01R04501.igs", "A01R04502.igs", "A01R04503.igs", "A01R04504.igs", "A01R04505.igs", "A01R04506.igs", "A01R04507.igs", "A01R04508.igs", "A01R04509.igs", "A01R04510.igs", "A01R04511.igs", "A01R04512.igs", "A01R04513.igs", "A01R04514.igs", "A01R04515.igs", "A01R04516.igs", "A01R04517.igs", "A01R04518.igs", "A01R04519.igs", "A01R04520.igs", "A01R04521.igs", "A01R04522.igs", "A01R04523.igs", "A01R04524.igs", "A01R04700.igs", "A01R04701.igs", "A01R04702.igs", "A01R04703.igs", "A01R04704.igs", "A01R04705.igs", "A01R04706.igs", "A01R04707.igs", "A01R04708.igs", "A01R04709.igs", "A01R04710.igs", "A01R04711.igs", "A01R04712.igs", "A01R04713.igs", "A01R04714.igs", "A01R04715.igs", "A01R04716.igs", "A01R04717.igs", "A01R04718.igs", "A01R04719.igs", "A01R04720.igs", "A01R04721.igs", "A01R04722.igs", "A01R04723.igs", "A01R04724.igs", "A01R04900.igs", "A01R04901.igs", "A01R04902.igs", "A01R04903.igs", "A01R04904.igs", "A01R04905.igs", "A01R04906.igs", "A01R04907.igs", "A01R04908.igs", "A01R04909.igs", "A01R04910.igs", "A01R04911.igs", "A01R04912.igs", "A01R04913.igs", "A01R04914.igs", "A01R04915.igs", "A01R04916.igs", "A01R04917.igs", "A01R04918.igs", "A01R04919.igs", "A01R04920.igs", "A01R04921.igs", "A01R04922.igs", "A01R04923.igs", "A01R04924.igs", "A01R05100.igs", "A01R05101.igs", "A01R05102.igs", "A01R05103.igs", "A01R05104.igs", "A01R05105.igs", "A01R05106.igs", "A01R05107.igs", "A01R05108.igs", "A01R05109.igs", "A01R05110.igs", "A01R05111.igs", "A01R05112.igs", "A01R05113.igs", "A01R05114.igs", "A01R05115.igs", "A01R05116.igs", "A01R05117.igs", "A01R05118.igs", "A01R05119.igs", "A01R05120.igs", "A01R05121.igs", "A01R05122.igs", "A01R05123.igs", "A01R05124.igs", "A01R05300.igs", "A01R05301.igs", "A01R05302.igs", "A01R05303.igs", "A01R05304.igs", "A01R05305.igs", "A01R05306.igs", "A01R05307.igs", "A01R05308.igs", "A01R05309.igs", "A01R05310.igs", "A01R05311.igs", "A01R05312.igs", "A01R05313.igs", "A01R05314.igs", "A01R05315.igs", "A01R05316.igs", "A01R05317.igs", "A01R05318.igs", "A01R05319.igs", "A01R05320.igs", "A01R05321.igs", "A01R05322.igs", "A01R05323.igs", "A01R05324.igs", "A01R05500.igs", "A01R05501.igs", "A01R05502.igs", "A01R05503.igs", "A01R05504.igs", "A01R05505.igs", "A01R05506.igs", "A01R05507.igs", "A01R05509.igs", "A01R05510.igs", "A01R05511.igs", "A01R05512.igs", "A01R05513.igs", "A01R05514.igs", "A01R05515.igs", "A01R05516.igs", "A01R05517.igs", "A01R05518.igs", "A01R05519.igs", "A01R05520.igs", "A01R05521.igs", "A01R05523.igs", "A01R05524.igs")

	For iterations = 0 To UBound(designNames) 
		Rhino.Command("SelAll")
		Rhino.Command("-SaveAs " & Chr(34) & "H:\152 DM-BAR tanker optimisation - General\C- Naval Arch\Dimension Reduction\design reconstrcution\deleteAnytime.3dm" & Chr(34) & " Enter")
		
		filePathName = Chr(34) & "H:\152 DM-BAR tanker optimisation - General\C- Naval Arch\Parametric model\01_GeometryBatches\Geos_20230905_1605_A01\igs\" & Cstr(designNames(iterations)) & Chr(34)
		Call Rhino.Command("_-Open " & filePathName, 0)
		
		Rhino.LayerColor "IGES level 1", RGB(0, 0, 0)
		Rhino.UnitSystem  4, True
		Rhino.ZoomExtents
		
		Rhino.Command("SelAll")
		Rhino.Command("Join")
		Rhino.Command("SelNon")
		
		Dim strHull:strHull = Rhino.ObjectsByType(16, False)(0)
		Dim arrMP:arrMP = Rhino.MeshParameters(1)
		Dim mesh:mesh = Rhino.MeshObjects(strHull, -1, arrMP)
		Rhino.MeshQuadsToTriangles mesh
		Rhino.DeleteObjects(strHull)
		
		Rhino.Command("_-SelMeshEdges SelMesh _Enter")
		Rhino.Command(" WeldEdge")
		Rhino.Command("SelMesh")
		Rhino.Command("!-_Export " & Chr(34) & "H:\152 DM-BAR tanker optimisation - General\C- Naval Arch\Dimension Reduction\meshed Designs\meshDesign" & CStr(iterations + 687) & ".stl" & Chr(34) & " _Enter _Enter")
	Next
End Sub


Function ReadTextFile
	Dim objFSO, objFile, strFileName, strLine
	Const ForReading = 1
 
	strFileName = "H:\Project with Prof Kaklis\01 BAR\fileNamesForRhino.csv"
	If IsNull(strFileName) Then Exit Function
 
	Set objFSO = CreateObject("Scripting.FileSystemObject")
	Set objFile = objFSO.OpenTextFile(strFileName, ForReading)
	Dim fileNames(), i 
	i = 0
	While Not objFile.AtEndOfStream
		strLine = objFile.ReadLine
		ReDim Preserve fileNames(i)
		fileNames(i) = strLine
		i = i + 1
	Wend
 
	objFile.Close
	Set objFSO = Nothing
	ReadTextFile = fileNames
End Function
