Option Explicit
'Script written by <insert name>
'Script copyrighted by <insert company name>
'Script version 29 August 2023 12:42:48

Call Main()
Sub Main()
	Dim numOfCurveDivPoints:numOfCurveDivPoints = 100
	Dim strHull, arrBox, Lwl, draft, beam, p1, p2, p3, i,j, arrParameter, patch_1(), patch_2(),patch_3(),patch_4(), s1, s2,s3, edgeCurves, temp_pts, patch_1234(),exp_s1_split, exp_s1_split_temp
	Dim temp_end, temp_start, test_pt, crvForPartStern, crvForPartStern_2, crvForPartStern_3, cutterLocation, edgePoint, doFlip
	Dim deckLines(), deckLines_, splitDeckLines, interPT, l1, l2, deckLine, deckPoints, supportLine, supportPTS, supportLength, supportPoints
	Dim sectionsAtForward(), sectionsAtMiddleBody, sectionsAtAft(), sectionsAtAft_segmented(), tempSet()
	Dim pointsAtForward(),pointsAtMiddleBody(), pointsAtAft()
	Dim pointsAtAft_temp, curveDivPoints, explodeCurves(), curveDivideNums
	Dim designNames:designNames = array("A01R00100.igs", "A01R00101.igs", "A01R00102.igs", "A01R00103.igs", "A01R00104.igs", "A01R00105.igs", "A01R00106.igs", "A01R00107.igs", "A01R00108.igs", "A01R00109.igs", "A01R00110.igs", "A01R00111.igs", "A01R00112.igs", "A01R00113.igs", "A01R00114.igs", "A01R00115.igs", "A01R00116.igs", "A01R00117.igs", "A01R00118.igs", "A01R00119.igs", "A01R00120.igs", "A01R00121.igs", "A01R00122.igs", "A01R00123.igs", "A01R00124.igs", "A01R00300.igs", "A01R00301.igs", "A01R00302.igs", "A01R00303.igs", "A01R00304.igs", "A01R00305.igs", "A01R00306.igs", "A01R00307.igs", "A01R00308.igs", "A01R00309.igs", "A01R00310.igs", "A01R00311.igs", "A01R00312.igs", "A01R00313.igs", "A01R00314.igs", "A01R00315.igs", "A01R00316.igs", "A01R00317.igs", "A01R00318.igs", "A01R00319.igs", "A01R00320.igs", "A01R00321.igs", "A01R00322.igs", "A01R00323.igs", "A01R00324.igs", "A01R00500.igs", "A01R00501.igs", "A01R00502.igs", "A01R00503.igs", "A01R00504.igs", "A01R00505.igs", "A01R00506.igs", "A01R00507.igs", "A01R00508.igs", "A01R00509.igs", "A01R00510.igs", "A01R00511.igs", "A01R00512.igs", "A01R00513.igs", "A01R00514.igs", "A01R00515.igs", "A01R00516.igs", "A01R00517.igs", "A01R00518.igs", "A01R00519.igs", "A01R00520.igs", "A01R00521.igs", "A01R00522.igs", "A01R00523.igs", "A01R00524.igs", "A01R00700.igs", "A01R00701.igs", "A01R00702.igs", "A01R00703.igs", "A01R00704.igs", "A01R00705.igs", "A01R00706.igs", "A01R00707.igs", "A01R00708.igs", "A01R00709.igs", "A01R00710.igs", "A01R00711.igs", "A01R00712.igs", "A01R00713.igs", "A01R00714.igs", "A01R00715.igs", "A01R00716.igs", "A01R00717.igs", "A01R00718.igs", "A01R00719.igs", "A01R00720.igs", "A01R00721.igs", "A01R00722.igs", "A01R00723.igs", "A01R00724.igs", "A01R00900.igs", "A01R00901.igs", "A01R00902.igs", "A01R00903.igs", "A01R00904.igs", "A01R00905.igs", "A01R00906.igs", "A01R00907.igs", "A01R00908.igs", "A01R00909.igs", "A01R00910.igs", "A01R00911.igs", "A01R00912.igs", "A01R00913.igs", "A01R00914.igs", "A01R00915.igs", "A01R00916.igs", "A01R00917.igs", "A01R00918.igs", "A01R00919.igs", "A01R00921.igs", "A01R00922.igs", "A01R00923.igs", "A01R00924.igs", "A01R01100.igs", "A01R01101.igs", "A01R01102.igs", "A01R01103.igs", "A01R01104.igs", "A01R01105.igs", "A01R01106.igs", "A01R01107.igs", "A01R01108.igs", "A01R01109.igs", "A01R01110.igs", "A01R01111.igs", "A01R01112.igs", "A01R01113.igs", "A01R01114.igs", "A01R01115.igs", "A01R01116.igs", "A01R01118.igs", "A01R01119.igs", "A01R01120.igs", "A01R01121.igs", "A01R01122.igs", "A01R01123.igs", "A01R01124.igs", "A01R01300.igs", "A01R01301.igs", "A01R01302.igs", "A01R01303.igs", "A01R01304.igs", "A01R01305.igs", "A01R01306.igs", "A01R01307.igs", "A01R01308.igs", "A01R01309.igs", "A01R01310.igs", "A01R01312.igs", "A01R01313.igs", "A01R01314.igs", "A01R01315.igs", "A01R01316.igs", "A01R01317.igs", "A01R01318.igs", "A01R01319.igs", "A01R01320.igs", "A01R01321.igs", "A01R01322.igs", "A01R01323.igs", "A01R01324.igs", "A01R01500.igs", "A01R01501.igs", "A01R01502.igs", "A01R01503.igs", "A01R01504.igs", "A01R01505.igs", "A01R01506.igs", "A01R01507.igs", "A01R01508.igs", "A01R01509.igs", "A01R01510.igs", "A01R01511.igs", "A01R01512.igs", "A01R01513.igs", "A01R01514.igs", "A01R01515.igs", "A01R01516.igs", "A01R01517.igs", "A01R01518.igs", "A01R01519.igs", "A01R01520.igs", "A01R01521.igs", "A01R01522.igs", "A01R01523.igs", "A01R01524.igs", "A01R01700.igs", "A01R01701.igs", "A01R01702.igs", "A01R01703.igs", "A01R01704.igs", "A01R01705.igs", "A01R01706.igs", "A01R01707.igs", "A01R01708.igs", "A01R01709.igs", "A01R01710.igs", "A01R01711.igs", "A01R01712.igs", "A01R01713.igs", "A01R01714.igs", "A01R01715.igs", "A01R01716.igs", "A01R01718.igs", "A01R01719.igs", "A01R01720.igs", "A01R01721.igs", "A01R01722.igs", "A01R01723.igs", "A01R01724.igs", "A01R01900.igs", "A01R01901.igs", "A01R01902.igs", "A01R01903.igs", "A01R01904.igs", "A01R01905.igs", "A01R01906.igs", "A01R01907.igs", "A01R01908.igs", "A01R01909.igs", "A01R01910.igs", "A01R01911.igs", "A01R01912.igs", "A01R01913.igs", "A01R01914.igs", "A01R01915.igs", "A01R01916.igs", "A01R01917.igs", "A01R01918.igs", "A01R01919.igs", "A01R01920.igs", "A01R01921.igs", "A01R01922.igs", "A01R01923.igs", "A01R01924.igs", "A01R02100.igs", "A01R02102.igs", "A01R02103.igs", "A01R02104.igs", "A01R02106.igs", "A01R02107.igs", "A01R02108.igs", "A01R02109.igs", "A01R02110.igs", "A01R02111.igs", "A01R02112.igs", "A01R02113.igs", "A01R02114.igs", "A01R02115.igs", "A01R02116.igs", "A01R02117.igs", "A01R02118.igs", "A01R02119.igs", "A01R02120.igs", "A01R02121.igs", "A01R02122.igs", "A01R02123.igs", "A01R02124.igs", "A01R02300.igs", "A01R02301.igs", "A01R02302.igs", "A01R02303.igs", "A01R02304.igs", "A01R02305.igs", "A01R02306.igs", "A01R02307.igs", "A01R02308.igs", "A01R02309.igs", "A01R02310.igs", "A01R02311.igs", "A01R02312.igs", "A01R02313.igs", "A01R02314.igs", "A01R02315.igs", "A01R02316.igs", "A01R02317.igs", "A01R02318.igs", "A01R02319.igs", "A01R02320.igs", "A01R02321.igs", "A01R02322.igs", "A01R02323.igs", "A01R02324.igs", "A01R02500.igs", "A01R02501.igs", "A01R02502.igs", "A01R02503.igs", "A01R02504.igs", "A01R02505.igs", "A01R02506.igs", "A01R02507.igs", "A01R02508.igs", "A01R02509.igs", "A01R02510.igs", "A01R02511.igs", "A01R02512.igs", "A01R02513.igs", "A01R02514.igs", "A01R02515.igs", "A01R02516.igs", "A01R02517.igs", "A01R02518.igs", "A01R02519.igs", "A01R02520.igs", "A01R02521.igs", "A01R02522.igs", "A01R02523.igs", "A01R02524.igs", "A01R02700.igs", "A01R02701.igs", "A01R02702.igs", "A01R02703.igs", "A01R02704.igs", "A01R02705.igs", "A01R02706.igs", "A01R02707.igs", "A01R02708.igs", "A01R02709.igs", "A01R02710.igs", "A01R02711.igs", "A01R02712.igs", "A01R02713.igs", "A01R02714.igs", "A01R02715.igs", "A01R02716.igs", "A01R02717.igs", "A01R02718.igs", "A01R02719.igs", "A01R02720.igs", "A01R02721.igs", "A01R02722.igs", "A01R02723.igs", "A01R02724.igs", "A01R02900.igs", "A01R02901.igs", "A01R02902.igs", "A01R02903.igs", "A01R02904.igs", "A01R02905.igs", "A01R02906.igs", "A01R02907.igs", "A01R02908.igs", "A01R02909.igs", "A01R02910.igs", "A01R02911.igs", "A01R02912.igs", "A01R02913.igs", "A01R02914.igs", "A01R02915.igs", "A01R02916.igs", "A01R02917.igs", "A01R02918.igs", "A01R02919.igs", "A01R02920.igs", "A01R02921.igs", "A01R02922.igs", "A01R02923.igs", "A01R02924.igs", "A01R03100.igs", "A01R03101.igs", "A01R03102.igs", "A01R03103.igs", "A01R03104.igs", "A01R03105.igs", "A01R03106.igs", "A01R03107.igs", "A01R03108.igs", "A01R03109.igs", "A01R03110.igs", "A01R03111.igs", "A01R03112.igs", "A01R03113.igs", "A01R03114.igs", "A01R03115.igs", "A01R03116.igs", "A01R03117.igs", "A01R03118.igs", "A01R03119.igs", "A01R03120.igs", "A01R03121.igs", "A01R03122.igs", "A01R03123.igs", "A01R03124.igs", "A01R03300.igs", "A01R03301.igs", "A01R03302.igs", "A01R03303.igs", "A01R03304.igs", "A01R03305.igs", "A01R03306.igs", "A01R03307.igs", "A01R03308.igs", "A01R03309.igs", "A01R03310.igs", "A01R03311.igs", "A01R03313.igs", "A01R03314.igs", "A01R03315.igs", "A01R03316.igs", "A01R03317.igs", "A01R03318.igs", "A01R03319.igs", "A01R03320.igs", "A01R03321.igs", "A01R03322.igs", "A01R03323.igs", "A01R03324.igs", "A01R03500.igs", "A01R03501.igs", "A01R03502.igs", "A01R03503.igs", "A01R03504.igs", "A01R03505.igs", "A01R03506.igs", "A01R03507.igs", "A01R03508.igs", "A01R03509.igs", "A01R03510.igs", "A01R03511.igs", "A01R03512.igs", "A01R03513.igs", "A01R03514.igs", "A01R03515.igs", "A01R03516.igs", "A01R03517.igs", "A01R03518.igs", "A01R03519.igs", "A01R03520.igs", "A01R03521.igs", "A01R03522.igs", "A01R03523.igs", "A01R03524.igs", "A01R03700.igs", "A01R03701.igs", "A01R03702.igs", "A01R03703.igs", "A01R03704.igs", "A01R03705.igs", "A01R03706.igs", "A01R03707.igs", "A01R03708.igs", "A01R03709.igs", "A01R03710.igs", "A01R03711.igs", "A01R03712.igs", "A01R03713.igs", "A01R03714.igs", "A01R03715.igs", "A01R03716.igs", "A01R03717.igs", "A01R03718.igs", "A01R03720.igs", "A01R03721.igs", "A01R03722.igs", "A01R03723.igs", "A01R03724.igs", "A01R03900.igs", "A01R03901.igs", "A01R03902.igs", "A01R03903.igs", "A01R03904.igs", "A01R03905.igs", "A01R03906.igs", "A01R03907.igs", "A01R03908.igs", "A01R03909.igs", "A01R03910.igs", "A01R03911.igs", "A01R03912.igs", "A01R03913.igs", "A01R03914.igs", "A01R03915.igs", "A01R03916.igs", "A01R03917.igs", "A01R03918.igs", "A01R03919.igs", "A01R03920.igs", "A01R03921.igs", "A01R03922.igs", "A01R03923.igs", "A01R03924.igs", "A01R04100.igs", "A01R04101.igs", "A01R04102.igs", "A01R04103.igs", "A01R04104.igs", "A01R04105.igs", "A01R04106.igs", "A01R04107.igs", "A01R04108.igs", "A01R04109.igs", "A01R04110.igs", "A01R04111.igs", "A01R04112.igs", "A01R04113.igs", "A01R04114.igs", "A01R04115.igs", "A01R04116.igs", "A01R04117.igs", "A01R04118.igs", "A01R04119.igs", "A01R04121.igs", "A01R04122.igs", "A01R04123.igs", "A01R04124.igs", "A01R04300.igs", "A01R04301.igs", "A01R04302.igs", "A01R04303.igs", "A01R04304.igs", "A01R04305.igs", "A01R04306.igs", "A01R04307.igs", "A01R04308.igs", "A01R04309.igs", "A01R04310.igs", "A01R04311.igs", "A01R04312.igs", "A01R04313.igs", "A01R04314.igs", "A01R04315.igs", "A01R04316.igs", "A01R04317.igs", "A01R04318.igs", "A01R04319.igs", "A01R04320.igs", "A01R04321.igs", "A01R04322.igs", "A01R04323.igs", "A01R04324.igs", "A01R04500.igs", "A01R04501.igs", "A01R04502.igs", "A01R04503.igs", "A01R04504.igs", "A01R04505.igs", "A01R04506.igs", "A01R04507.igs", "A01R04508.igs", "A01R04509.igs", "A01R04510.igs", "A01R04511.igs", "A01R04512.igs", "A01R04513.igs", "A01R04514.igs", "A01R04515.igs", "A01R04516.igs", "A01R04517.igs", "A01R04518.igs", "A01R04519.igs", "A01R04520.igs", "A01R04521.igs", "A01R04522.igs", "A01R04523.igs", "A01R04524.igs", "A01R04700.igs", "A01R04701.igs", "A01R04702.igs", "A01R04703.igs", "A01R04704.igs", "A01R04705.igs", "A01R04706.igs", "A01R04707.igs", "A01R04708.igs", "A01R04709.igs", "A01R04710.igs", "A01R04711.igs", "A01R04712.igs", "A01R04713.igs", "A01R04714.igs", "A01R04715.igs", "A01R04716.igs", "A01R04717.igs", "A01R04718.igs", "A01R04719.igs", "A01R04720.igs", "A01R04721.igs", "A01R04722.igs", "A01R04723.igs", "A01R04724.igs", "A01R04900.igs", "A01R04901.igs", "A01R04902.igs", "A01R04903.igs", "A01R04904.igs", "A01R04905.igs", "A01R04906.igs", "A01R04907.igs", "A01R04908.igs", "A01R04909.igs", "A01R04910.igs", "A01R04911.igs", "A01R04912.igs", "A01R04913.igs", "A01R04914.igs", "A01R04915.igs", "A01R04916.igs", "A01R04917.igs", "A01R04918.igs", "A01R04919.igs", "A01R04920.igs", "A01R04921.igs", "A01R04922.igs", "A01R04923.igs", "A01R04924.igs", "A01R05100.igs", "A01R05101.igs", "A01R05102.igs", "A01R05103.igs", "A01R05104.igs", "A01R05105.igs", "A01R05106.igs", "A01R05107.igs", "A01R05108.igs", "A01R05109.igs", "A01R05110.igs", "A01R05111.igs", "A01R05112.igs", "A01R05113.igs", "A01R05114.igs", "A01R05115.igs", "A01R05116.igs", "A01R05117.igs", "A01R05118.igs", "A01R05119.igs", "A01R05120.igs", "A01R05121.igs", "A01R05122.igs", "A01R05123.igs", "A01R05124.igs", "A01R05300.igs", "A01R05301.igs", "A01R05302.igs", "A01R05303.igs", "A01R05304.igs", "A01R05305.igs", "A01R05306.igs", "A01R05307.igs", "A01R05308.igs", "A01R05309.igs", "A01R05310.igs", "A01R05311.igs", "A01R05312.igs", "A01R05313.igs", "A01R05314.igs", "A01R05315.igs", "A01R05316.igs", "A01R05317.igs", "A01R05318.igs", "A01R05319.igs", "A01R05320.igs", "A01R05321.igs", "A01R05322.igs", "A01R05323.igs", "A01R05324.igs", "A01R05500.igs", "A01R05501.igs", "A01R05502.igs", "A01R05503.igs", "A01R05504.igs", "A01R05505.igs", "A01R05506.igs", "A01R05507.igs", "A01R05509.igs", "A01R05510.igs", "A01R05511.igs", "A01R05512.igs", "A01R05513.igs", "A01R05514.igs", "A01R05515.igs", "A01R05516.igs", "A01R05517.igs", "A01R05518.igs", "A01R05519.igs", "A01R05520.igs", "A01R05521.igs", "A01R05523.igs", "A01R05524.igs")

	''''' "£$^"£$*%"(£$%"£*$ Remember there is 687 is added to the saved files ~~~~~~~~~~~~"£$%("£$*%"£($%*"£$%(
	Dim iterations
	For iterations = 1 To 1'UBOund(designNames)

		doFlip = False
		Rhino.Command("SelAll")
		Rhino.Command("Delete")
		Rhino.Command("-SaveAs " & Chr(34) & "H:\152 DM-BAR tanker optimisation - General\C- Naval Arch\Dimension Reduction\tempCreation_divideCurve.3dm" & Chr(34) & " Enter")
		'Dim filePathName:filePathName = Chr(34) & "H:\152 DM-BAR tanker optimisation - General\C- Naval Arch\Dimension Reduction\design_" & Cstr(iterations) & ".3dm" & Chr(34)
		Dim filePathName:filePathName = Chr(34) & "H:\152 DM-BAR tanker optimisation - General\C- Naval Arch\Dimension Reduction\released_hulls_igs\BAR_reg1pct_125kDWT.igs" & Chr(34)
		Call Rhino.Command("_-Open " & filePathName, 0)
		Rhino.Command "-_MaxViewport", 0 ' 0 means no echo
		Rhino.LayerColor "IGES level 1", RGB(0, 0, 0)
		Rhino.UnitSystem  4, True
		Rhino.ZoomExtents
		Rhino.Command("SelAll")
		Rhino.Command("Join _Enter")
		Rhino.Command("SelNone")
		
		
		strHull = Rhino.ObjectsByType(16, False)(0)

		arrBox = Rhino.BoundingBox(strHull)
		Lwl = abs(arrBox(4)(0) - arrBox(5)(0))
		draft = abs(arrBox(0)(2) - arrBox(4)(2))
		beam = abs(arrBox(0)(1) - arrBox(2)(1))
	
		p3 = array(arrBox(4), array(Lwl * 0.05, arrBox(4)(1), arrBox(4)(2)))
		p2 = array(array(Lwl * 0.05, arrBox(4)(1), arrBox(4)(2)), array(Lwl * 0.9, arrBox(4)(1), arrBox(4)(2)))
		p1 = array(array(Lwl * 0.9, arrBox(4)(1), arrBox(4)(2)), array(arrBox(5)(0), arrBox(4)(1), arrBox(4)(2)))
		
		'Rhino.AddLine p3(0), p3(1)
		'Rhino.AddLine p2(0), p2(1)
		'Rhino.AddLine p1(0), p1(1)
		s1 = Rhino.AddCutPlane(strHull, p3(1), array(p3(1)(0), 0, 0), array(0, 1, 0))
		s2 = Rhino.AddCutPlane(strHull, p1(0), array(p1(0)(0), 0, 0), array(0, 1, 0))
		
		'+++++++++++++++++++++++++++++++++++++++++++++++++++++++++++++++++++++
		'+++++++++++++++ Forward Part ++++++++++++++++++++++++++++++++++++++
		'+++++++++++++++++++++++++++++++++++++++++++++++++++++++++++++++++++++
		
		'''' from the he code is for deck """""""""""""""""""""""""""""""""""""""
		ReDim deckLines(0)
		edgeCurves = Rhino.DuplicateEdgeCurves(strHull, False)
		For i = 0 To UBound(edgeCurves)
			temp_end = Rhino.CurveEndPoint(edgeCurves(i))
			temp_start = Rhino.CurveStartPoint(edgeCurves(i))
			If abs(temp_end(2) - p1(1)(2)) < 0.00001 And abs(temp_start(2) - p1(1)(2)) < 0.00001 Then
				deckLines(UBound(deckLines)) = Rhino.CopyObject(edgeCurves(i))
				ReDim Preserve deckLines(UBound(deckLines)+1)
			End If
		Next
		ReDim Preserve deckLines(UBound(deckLines)-1)
		deckLines_ = Rhino.JoinCurves(deckLines, True)(0)
		
		interPT = Rhino.CurveSurfaceIntersection(deckLines_, s2)
		splitDeckLines = Rhino.SplitCurve(deckLines_, interPT(0, 6), True)
		l1 = Rhino.CurveLength(splitDeckLines(0))
		l2 = Rhino.CurveLength(splitDeckLines(1))
		If l1 < l2 Then 
			deckLine = Rhino.CopyObject(splitDeckLines(0))
		Else
			deckLine = Rhino.CopyObject(splitDeckLines(1))
		End If
		Rhino.DeleteObjects edgeCurves
		Rhino.DeleteObjects splitDeckLines
		ReDim supportPTS(1)

		temp_end = Rhino.CurveEndPoint(deckLine)
		temp_start = Rhino.CurveStartPoint(deckLine)
		If temp_start(0) > temp_end(0) Then
			supportPTS(0) = temp_start
			supportPTS(1) = array(temp_end(0), temp_start(1), temp_start(2))
		Else
			supportPTS(0) = temp_end
			supportPTS(1) = array(temp_start(0), temp_end(1), temp_end(2))
		End If
	
		supportLength = abs(supportPTS(1)(0) - supportPTS(0)(0))
		supportLine = Rhino.AddLine(supportPTS(1), array(supportPTS(1)(0) + (supportLength / 3), supportPTS(0)(1), supportPTS(0)(2)))

		If temp_start(0) > temp_end(0) Then
			Rhino.ReverseCurve deckLine
			doFlip = True
		End If
		
		deckPoints = Rhino.DivideCurve(deckLine, 20)
		supportPoints = Rhino.DivideCurve(supportLine, 20)
		Rhino.DeleteObjects array(supportLine, deckLine)
		
		ReDim sectionsAtForward(0)
		For i = 1 To UBound(deckPoints)
			l1 = Rhino.ExtendCurveLength(Rhino.AddLine(deckPoints(i), supportPoints(i)), 0, 0, 20)
			l2 = Rhino.AddLine(deckPoints(i), array(deckPoints(i)(0), deckPoints(i)(1), -10))
			s3 = Rhino.ExtrudeCurve(l1, l2)
			sectionsAtForward(UBound(sectionsAtForward)) = Rhino.IntersectBreps(strHull, s3)(0)
			ReDim Preserve sectionsAtForward(UBound(sectionsAtForward)+1)
			Rhino.DeleteObjects array(s3, l1, l2)
		Next
		ReDim Preserve sectionsAtForward(UBound(sectionsAtForward)-1)
		''''"""""""""""""""""""""""""""""""""""""""
		
		'+++++++++++++++++++++++++++++++++++++++++++++++++++++++++++++++++++++
		'+++++++++++++++ Aft Part ++++++++++++++++++++++++++++++++++++++
		'+++++++++++++++++++++++++++++++++++++++++++++++++++++++++++++++++++++
		
		Dim s1_split:s1_split = Rhino.SplitBrep(strHull, s1, True)

		Rhino.DeleteObject(s1)
	
		exp_s1_split_temp = Rhino.ExplodePolysurfaces(s1_split(0), True)
		exp_s1_split = exp_s1_split_temp
		
		exp_s1_split(0) = exp_s1_split_temp(0)
		exp_s1_split(3) = exp_s1_split_temp(1)
		exp_s1_split(1) = exp_s1_split_temp(2)
		exp_s1_split(4) = exp_s1_split_temp(3)
		exp_s1_split(2) = exp_s1_split_temp(4)

		If doFlip = True Then
			For i = 0 To UBound(exp_s1_split)
				Rhino.FlipSurface exp_s1_split(i), True
			Next
			doFlip = False
		End If
		
		If UBound(exp_s1_split) = 4 Then
			
			'------------------------------------------------------------------
			edgeCurves = Rhino.DuplicateEdgeCurves(exp_s1_split(1), False)
			ReDim Preserve patch_1(0)
			' To select the top curve of this patch
			Dim lastCurve
			For i = 0 To Ubound(edgeCurves)
				temp_end = Rhino.CurveEndPoint(edgeCurves(i))
				temp_start = Rhino.CurveStartPoint(edgeCurves(i))	
				If temp_end(2) > 4 And temp_start(2) > 4 And abs(temp_end(0) - temp_start(0)) > 5 Then
					temp_pts = Rhino.DivideCurve(edgeCurves(i), 20)
					If Rhino.CurveStartPoint(edgeCurves(2))(0) > Rhino.CurveEndPoint(edgeCurves(2))(0) Then
						test_pt = Rhino.CurveEndPoint(edgeCurves(i))
					Else
						test_pt = Rhino.CurveStartPoint(edgeCurves(i))
					End If
				End If
				If abs(temp_end(0) - temp_start(0)) < 0.001 Then
					patch_1(0) = Rhino.CopyObject(edgeCurves(i))
				End If 
				If abs(temp_end(0) - temp_start(0)) > 0.001 And abs(temp_end(2) - temp_start(2)) > 4 And (temp_end(2) < 0.001 Or temp_start(2) < 0.001) Then
					lastCurve = Rhino.CopyObject(edgeCurves(i))
				End If 
			Next
	
			For i = 1 To UBound(temp_pts) - 1
				ReDim Preserve patch_1(i)
				arrParameter = Rhino.SurfaceClosestPoint(exp_s1_split(1), temp_pts(i))
				patch_1(i) = Rhino.ExtractIsoCurve(exp_s1_split(1), arrParameter, 0)(0)
			Next
			ReDim Preserve patch_1(UBound(patch_1)+1)
			patch_1(UBound(patch_1)) = lastCurve
			Rhino.DeleteObjects(edgeCurves)
			'------------------------------------------------------------------
			
			'===================================================================================================
			' Getting curves at the small bend at the stern
			edgeCurves = Rhino.DuplicateEdgeCurves(exp_s1_split(0), False)	
			For i = 0 To Ubound(edgeCurves)
				temp_end = Rhino.CurveEndPoint(edgeCurves(i))
				temp_start = Rhino.CurveStartPoint(edgeCurves(i))	
				If temp_end(1) < 0.00001 And temp_start(1) < 0.00001 And abs(temp_end(2) - temp_start(2)) > 4  Then
					ReDim Preserve patch_1(UBound(patch_1)+1)
					patch_1(UBound(patch_1)) = Rhino.CopyObject(edgeCurves(i))
					ReDim Preserve temp_pts(UBound(temp_pts)+1)
					If temp_end(2) > temp_start(2) Then
						temp_pts(UBound(temp_pts)) = temp_end
					Else
						temp_pts(UBound(temp_pts)) = temp_start
					End If
				End If
			Next
			Rhino.DeleteObjects(edgeCurves)
			'===================================================================================================
	
			' ++++++++++++++++++++++++++++++++++++++++++++++++++++++++++++++++
			' selecting the first curves of patch/exp_s1_split 2 and 4 (see note book for the their numbering )
			ReDim Preserve patch_2(0)
			edgeCurves = Rhino.DuplicateEdgeCurves(exp_s1_split(4), False)
			For i = 0 To UBound(edgeCurves)
				temp_end = Rhino.CurveEndPoint(edgeCurves(i))
				temp_start = Rhino.CurveStartPoint(edgeCurves(i))		
				If abs(temp_end(0) - temp_start(0)) < 0.001 And temp_start(0) > 0 And temp_end(0) > 0 Then
					patch_2(0) = Rhino.CopyObject(edgeCurves(i))
				End If 
				If temp_end(1) < 0.00001 And temp_start(1) < 0.00001 And (temp_start(0) < 0 Or temp_end(0) < 0) Then
					crvForPartStern = Rhino.CopyObject(edgeCurves(i))
				End If
				If temp_start(0) < 0 And temp_end(0) < 0 Then
					crvForPartStern_2 = Rhino.CopyObject(edgeCurves(i))
				End If
			Next
			Rhino.DeleteObjects(edgeCurves)
			
			ReDim Preserve patch_3(0)
			edgeCurves = Rhino.DuplicateEdgeCurves(exp_s1_split(2), False)
			For i = 0 To UBound(edgeCurves)
				temp_end = Rhino.CurveEndPoint(edgeCurves(i))
				temp_start = Rhino.CurveStartPoint(edgeCurves(i))		
				If abs(temp_end(0) - temp_start(0)) < 0.001 And temp_start(0) > 0 And temp_end(0) > 0 Then
					patch_3(0) = Rhino.CopyObject(edgeCurves(i))
				End If 
				If temp_start(0) < 0 And temp_end(0) < 0 Then
					crvForPartStern_3 = Rhino.CopyObject(edgeCurves(i))
				End If
			Next
			Rhino.DeleteObjects(edgeCurves)

			' Getting iso cruves for 2 and 4 patches/exp_s1_split (see note book for the their numbering )
			For i = 1 To UBound(temp_pts)
				ReDim Preserve patch_2(i)
				ReDim Preserve patch_3(i)
				arrParameter = Rhino.SurfaceClosestPoint(exp_s1_split(4), temp_pts(i))
				patch_2(i) = Rhino.ExtractIsoCurve(exp_s1_split(4), arrParameter, 0)(0)
				
				temp_end = Rhino.CurveEndPoint(patch_2(i))
				temp_start = Rhino.CurveStartPoint(patch_2(i))
				If temp_start(2) > temp_end(2) Then 
					arrParameter = Rhino.SurfaceClosestPoint(exp_s1_split(2), temp_start)
				Else
					arrParameter = Rhino.SurfaceClosestPoint(exp_s1_split(2), temp_end)
				End If
				patch_3(i) = Rhino.ExtractIsoCurve(exp_s1_split(2), arrParameter, 0)(0)
			Next	
			'++++++++++++++++++++++++++++++++++++++++++++++++++++++++++++++++++++++++++++++
		
			'%%%%%%%%%%%%%%%%%%%%%%%%%%%%%%%%%%%%%%%%%%%%%%%%%%%%%%%%%%%%%%%%%%%%%%%%%%%%%%%%%%%%
			' Here we are adding the very first curve
			ReDim Preserve patch_4(0)
			temp_end = Rhino.CurveEndPoint(patch_1(0))
			temp_start = Rhino.CurveStartPoint(patch_1(0))
			If temp_start(2) < temp_end(2) Then 
				patch_4(0) = Rhino.AddLine(temp_start, array(temp_start(0), 0, temp_start(2)))
			Else
				patch_4(0) = Rhino.AddLine(temp_end, array(temp_end(0), 0, temp_end(2)))
			End If
			' Here we are adding the remaining curves
			For i = 1 To UBound(patch_1) - 1
				temp_end = Rhino.CurveEndPoint(patch_1(i))
				temp_start = Rhino.CurveStartPoint(patch_1(i))
				ReDim Preserve patch_4(i)
				If temp_start(2) < temp_end(2) Then 
					arrParameter = Rhino.SurfaceClosestPoint(exp_s1_split(3), temp_start)
				Else
					arrParameter = Rhino.SurfaceClosestPoint(exp_s1_split(3), temp_end)
				End If
				patch_4(i) = Rhino.ExtractIsoCurve(exp_s1_split(3), arrParameter, 1)(0)
			Next
			'%%%%%%%%%%%%%%%%%%%%%%%%%%%%%%%%%%%%%%%%%%%%%%%%%%%%%%%%%%%%%%%%%%%%%%%%%%%%%%%%%%%%
			
			' Joining all the curves
			For i = 0 To UBound(patch_1) - 1
				ReDim Preserve patch_1234(i)
				patch_1234(i) = Rhino.JoinCurves(array(patch_1(i), patch_2(i), patch_3(i), patch_4(i)))(0)
			Next
			ReDim Preserve patch_1234(UBound(patch_1234)+1)
			patch_1234(UBound(patch_1234)) = Rhino.JoinCurves(array(patch_1(UBound(patch_1)), patch_2(UBound(patch_2)), patch_3(UBound(patch_3))))(0)
			
			
			' From here we are doing calcualtion of the patch after the stern to the left not towards hull
			temp_pts = Rhino.DivideCurve(crvForPartStern, 20)			
			
			For i = 1 To UBound(temp_pts) - 1
				ReDim Preserve patch_2(UBound(patch_2)+1)
				arrParameter = Rhino.SurfaceClosestPoint(exp_s1_split(4), temp_pts(UBound(temp_pts) - i))
				patch_2(UBound(patch_2)) = Rhino.ExtractIsoCurve(exp_s1_split(4), arrParameter, 0)(0)
				
				temp_end = Rhino.CurveEndPoint(patch_2(UBound(patch_2)))
				temp_start = Rhino.CurveStartPoint(patch_2(UBound(patch_2)))
				ReDim Preserve patch_3(UBound(patch_3)+1)
				If temp_start(2) > temp_end(2) Then 
					arrParameter = Rhino.SurfaceClosestPoint(exp_s1_split(2), temp_start)
				Else
					arrParameter = Rhino.SurfaceClosestPoint(exp_s1_split(2), temp_end)
				End If
				patch_3(UBound(patch_3)) = Rhino.ExtractIsoCurve(exp_s1_split(2), arrParameter, 0)(0)
		
				ReDim Preserve patch_1234(Ubound(patch_1234)+1)
				patch_1234(Ubound(patch_1234)) = Rhino.JoinCurves(array(patch_2(UBound(patch_2)), patch_3(UBound(patch_3))))(0)
			Next
			ReDim Preserve patch_2(UBound(patch_2)+1)
			ReDim Preserve patch_3(UBound(patch_3)+1)
			patch_2(UBound(patch_2)) = Rhino.CopyObject(crvForPartStern_2)
			patch_3(UBound(patch_3)) = Rhino.CopyObject(crvForPartStern_3)
			ReDim Preserve patch_1234(Ubound(patch_1234)+1)
			patch_1234(Ubound(patch_1234)) = Rhino.JoinCurves(array(patch_2(UBound(patch_2)), patch_3(UBound(patch_3))))(0)
			
			' Because all the curves reversed so we are adding to a new variable sectionsAtAft This is also to maintain consistancy throughout the three sections
			ReDim sectionsAtAft(0)
			For i = 0 To UBound(patch_1234)
				sectionsAtAft(UBound(sectionsAtAft)) = Rhino.CopyObject(patch_1234(UBound(patch_1234) - i))
				ReDim Preserve sectionsAtAft(UBound(sectionsAtAft)+1)
			Next
			ReDim Preserve sectionsAtAft(UBound(sectionsAtAft)-1)
			Rhino.DeleteObjects(patch_1234)
			
			'----------------- saving unjoined sections in the reverse order-------------------------------------------------
			ReDim sectionsAtAft_segmented(3)
			ReDim tempSet(0)
			For i = 0 To UBound(patch_3)
				tempSet(UBound(tempSet)) = Rhino.CopyObject(patch_3(UBound(patch_3) - i))
				ReDim Preserve tempSet(UBound(tempSet)+1)
			Next
			ReDim Preserve tempSet(UBound(tempSet)-1)
			sectionsAtAft_segmented(0) = tempSet
			
			ReDim tempSet(0)
			For i = 0 To UBound(patch_2)
				tempSet(UBound(tempSet)) = Rhino.CopyObject(patch_2(UBound(patch_2) - i))
				ReDim Preserve tempSet(UBound(tempSet)+1)
			Next
			ReDim Preserve tempSet(UBound(tempSet)-1)
			sectionsAtAft_segmented(1) = tempSet			
			
			ReDim tempSet(0)
			For i = 0 To UBound(patch_1)
				tempSet(UBound(tempSet)) = Rhino.CopyObject(patch_1(UBound(patch_1) - i))
				ReDim Preserve tempSet(UBound(tempSet)+1)
			Next
			ReDim Preserve tempSet(UBound(tempSet)-1)
			sectionsAtAft_segmented(2) = tempSet				
			
			ReDim tempSet(0)
			For i = 0 To UBound(patch_4)
				tempSet(UBound(tempSet)) = Rhino.CopyObject(patch_4(UBound(patch_4) - i))
				ReDim Preserve tempSet(UBound(tempSet)+1)
			Next
			ReDim Preserve tempSet(UBound(tempSet)-1)
			sectionsAtAft_segmented(3) = tempSet
			'------------------------------------------------------------------------------------------------------------------
			
			' If you dont want to delete the unjoined curves comment these four line
			Rhino.DeleteObjects(patch_1)
			Rhino.DeleteObjects(patch_2)
			Rhino.DeleteObjects(patch_3)
			Rhino.DeleteObjects(patch_4)
			
			Rhino.DeleteObjects(array(crvForPartStern, crvForPartStern_2, crvForPartStern_3))

			strHull = Rhino.JoinSurfacesEx(exp_s1_split, True)
			strHull = Rhino.ObjectsByType(16, True)
			strHull = Rhino.JoinSurfacesEx(strHull, True)(0)
	
			'+++++++++++++++++++++++++++++++++++++++++++++++++++++++++++++++++++++
			'+++++++++++++++ middle body Part ++++++++++++++++++++++++++++++++++++++
			'+++++++++++++++++++++++++++++++++++++++++++++++++++++++++++++++++++++
			
			' From here we are doing calculation for the part of the middle body
			Dim stepSize:stepSize = abs(p1(0)(0) - p3(1)(0)) / 50
			sectionsAtMiddleBody = Rhino.AddSrfContourCrvs(strHull, array(p3(1)(0) + stepSize, p3(1)(1), p3(1)(2)), p1(0), stepSize)
			
			If UBound(sectionsAtMiddleBody) + 1 <> 50 Then
				ReDim Preserve sectionsAtMiddleBody(UBound(sectionsAtMiddleBody)+1)
				sectionsAtMiddleBody(UBound(sectionsAtMiddleBody)) = Rhino.IntersectBreps(strHull, s2)(0)
			End If
			Rhino.DeleteObject s2

			'cutterLocation = p3(1)
			'ReDim sectionsAtMiddleBody(0)
			'For i = 0 To 99
			'	cutterLocation(0) = cutterLocation(0) + stepSize
			'	s1 = Rhino.AddCutPlane(strHull, cutterLocation, array(cutterLocation(0), 0, 0), array(0, 1, 0))
			'	sectionsAtMiddleBody(UBound(sectionsAtMiddleBody)) = Rhino.IntersectBreps(strHull, s1)(0)
			'	ReDim Preserve sectionsAtMiddleBody(UBound(sectionsAtMiddleBody)+1)
			'	Rhino.DeleteObject(s1)
			'Next
			'ReDim Preserve sectionsAtMiddleBody(UBound(sectionsAtMiddleBody)-1)
			
			
			
			'+++++++++++++++++++++++++++++++++++++++++++++++++++++++++++++++++++++
			'+++++++++++++++ Getting Points on Curves ++++++++++++++++++++++++++++++++++++++
			'+++++++++++++++++++++++++++++++++++++++++++++++++++++++++++++++++++++
			
			Rhino.DeleteObjects sectionsAtAft ' This temprary
			'pointsAtForward(),pointsAtMiddleBody()
			ReDim pointsAtAft(UBound(sectionsAtAft_segmented))
			curveDivideNums = array(18, 52, 28, 2)
			ReDim explodeCurves(3)
			For i = 0 To UBound(sectionsAtAft_segmented)
				ReverseCurvesDirectionDownward sectionsAtAft_segmented(i)
				explodeCurves(i) = Rhino.CopyObject(sectionsAtAft_segmented(i)(UBOund(sectionsAtAft_segmented(i))))
				ReDim pointsAtAft_temp(UBound(sectionsAtAft_segmented(i)))
				For j = 0 To UBound(sectionsAtAft_segmented(i))
					pointsAtAft_temp(j) = Rhino.DivideCurve(sectionsAtAft_segmented(i)(j), curveDivideNums(i))
					'Rhino.DeleteObject sectionsAtAft_segmented(i)(j)
					'sectionsAtAft_segmented(i)(j) = Rhino.AddInterpCurveEx(pointsAtAft_temp(j))
				Next
				pointsAtAft(i) = pointsAtAft_temp
				'Rhino.AddLoftSrf sectionsAtAft_segmented(i), , , 3, 0
			Next
			
			ReDim pointsAtMiddleBody(UBound(sectionsAtMiddleBody))
			ReverseCurvesDirectionDownward sectionsAtMiddleBody
			
			For i = 0 To UBound(sectionsAtMiddleBody)
				pointsAtMiddleBody(i) = Rhino.DivideCurve(sectionsAtMiddleBody(i), numOfCurveDivPoints)
				'Rhino.DeleteObject sectionsAtMiddleBody(i)
				'sectionsAtMiddleBody(i) = Rhino.AddInterpCurveEx(pointsAtMiddleBody(i))
			Next
			'Rhino.AddLoftSrf sectionsAtMiddleBody, , , 3, 0
			
			ReDim pointsAtForward(UBound(sectionsAtForward))
			ReverseCurvesDirectionDownward sectionsAtForward
			For i = 0 To UBound(sectionsAtForward)
				pointsAtForward(i) = Rhino.DivideCurve(sectionsAtForward(i), numOfCurveDivPoints)
				'Rhino.DeleteObject sectionsAtForward(i)
				'sectionsAtForward(i) = Rhino.AddInterpCurveEx(pointsAtForward(i))
			Next
			'Rhino.AddLoftSrf sectionsAtForward, , , 3, 0
			'Rhino.AddLoftSrf array(sectionsAtMiddleBody(UBound(sectionsAtMiddleBody)), sectionsAtForward(0)), , , 3, 0
			
			
			'+++++++++++++++++++++++++++++++++++++++++++++++++++++++++++++++++++++
			'+++++++++++++++ Storing all the points in a file ++++++++++++++++++++++++++++++++++++++
			'+++++++++++++++++++++++++++++++++++++++++++++++++++++++++++++++++++++			
			
			
			'Saving points to a file
			'Get the file system object
			Dim objFSO, objStream
			Set objFSO = CreateObject("Scripting.FileSystemObject")

			' Open a text file to write to
			Set objStream = objFSO.CreateTextFile("C:\Users\Shahroz.Khan\OneDrive - BA Technologies Ltd\Documents\BAR_reg1pct_125kDWT.txt", True)
			
			' Write each point as text to the file
			Dim strPoint, strText
			
			For i = 0 To UBound(pointsAtAft)
				For j =0 To UBound(pointsAtAft(i))
					For Each strPoint In pointsAtAft(i)(j)
						strText = Rhino.Pt2Str(strPoint)
						objStream.WriteLine(strText)
					Next
				Next
			Next

			For i = 0 To UBound(pointsAtMiddleBody)
				For Each strPoint In pointsAtMiddleBody(i)
					strText = Rhino.Pt2Str(strPoint)
					objStream.WriteLine(strText)
				Next
			Next
			
			For i = 0 To UBound(pointsAtForward)
				For Each strPoint In pointsAtForward(i)
					strText = Rhino.Pt2Str(strPoint)
					objStream.WriteLine(strText)
				Next
			Next			
			
			objStream.Close
			
			Rhino.DeleteObject strHull
			Rhino.Print("All Curves: " & CStr(UBound(Rhino.ObjectsByType(4, True))))
			
			'If UBound(Rhino.ObjectsByType(4, True)) <> 261 Then
			'	Dim strMessage
			'	strMessage = "Problem!"
			'	Rhino.MessageBox strMessage, 64, "Title of the MessageBox"
			'End If 
		Else
			Rhino.Print("Didnt work ++++++++++++++++++++++++++++++++++++++++++++++++++++++")
		End If
		Rhino.Command("_ClearUndo")
	Next
End Sub

Function ReplaceClosestPoint(arrPoints, ptInput)
	Dim index, i
	Dim minDistance, currentDistance

	' Initialize minimum distance with a large value
	minDistance = Rhino.Distance(arrPoints(0), ptInput)
	index = 0

	' Iterate through the array of points to find the closest one
	For i = 1 To UBound(arrPoints)
		currentDistance = Rhino.Distance(arrPoints(i), ptInput)
		If currentDistance < minDistance Then
			minDistance = currentDistance
			index = i
		End If
	Next

	' Replace the closest point with the input point
	arrPoints(index) = ptInput
    
	ReplaceClosestPoint = arrPoints
End Function

Function getEndPoint_wrt_z_axis(curve)
	Dim temp_end:temp_end = Rhino.CurveEndPoint(curve)
	Dim temp_start:temp_start = Rhino.CurveStartPoint(curve)
	If temp_start(2) < temp_end(2) Then 
		getEndPoint_wrt_z_axis = temp_start
	Else
		getEndPoint_wrt_z_axis = temp_end
	End If
End Function

Function getStartPoint_wrt_z_axis(curve)
	Dim temp_end:temp_end = Rhino.CurveEndPoint(curve)
	Dim temp_start:temp_start = Rhino.CurveStartPoint(curve)
	If temp_start(2) > temp_end(2) Then 
		getStartPoint_wrt_z_axis = temp_start
	Else
		getStartPoint_wrt_z_axis = temp_end
	End If
End Function

Function start_end_points(arrCurves)
	Dim i, allPoints()
	ReDim allPoints(0)
	For i = 0 To UBound(arrCurves)
		allPoints(UBound(allPoints)) = Rhino.CurveStartPoint(arrCurves(i))
		ReDim Preserve allPoints(UBound(allPoints)+1)
		allPoints(UBound(allPoints)) = Rhino.CurveStartPoint(arrCurves(i))
		ReDim Preserve allPoints(UBound(allPoints)+1)
	Next
	ReDim Preserve allPoints(UBound(allPoints)-1)
	start_end_points = allPoints
End Function

Function ReverseCurvesDirectionDownward(arrCurves)
	Dim i, ptStart, ptEnd
    
	For i = 0 To UBound(arrCurves)
		ptStart = Rhino.CurveStartPoint(arrCurves(i))
		ptEnd = Rhino.CurveEndPoint(arrCurves(i))
        
		' Check if the curve is facing upwards based on Z-values
		If ptStart(2) < ptEnd(2) Then 
			' If the curve is facing upwards, reverse the curve
			Rhino.ReverseCurve arrCurves(i)
		End If
	Next
End Function
