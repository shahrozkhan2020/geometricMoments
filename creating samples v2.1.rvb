Option Explicit
'Script written by <insert name>
'Script copyrighted by <insert company name>
'Script version 01 September 2023 16:31:25

Call Main()
Sub Main()
	Rhino.Command("SelAll")
	Rhino.Command("Delete")
	Dim desNo, pointSet,ptCrv(), strCrv, i, j, k, m, temp, stern(), totalNoOfPtsOnEachCrv, endPtForLoft, temp_end(), temp_start(), n
	Dim checkPoints(), checkCurves(), checkCrvJoin, checkCrvDivid
	Dim curvesInEachPatch, surfaces()
	Dim numOfPointsInCurve, firstCurve, ptCrv_temp, strCrv_temp(), lastCrvOfPatch2
	
	For desNo = 30 To 30
		ReDim checkPoints(0), checkCurves(0)
		Rhino.Print("Design ++++++++++++++++++++: " & Cstr(desNo))
		totalNoOfPtsOnEachCrv = 100
		numOfPointsInCurve = array(19, 53, 53, 29, 3, 101)
		curvesInEachPatch = array(42, 21, 21, 22, 21, 71) ' last element here will selctions at middle + 21; If then senction at midddle are 100 then it should be 100+21
		
		n = 0
		ReDim stern(1)
		firstCurve = False
		ReDim strCrv_temp(3)
		Rhino.Command("SelAll")
		Rhino.Command("Delete")
		
		pointSet = ImportPoints("C:\Users\Shahroz.Khan\OneDrive - BA Technologies Ltd\Documents\Design Points_" & CStr(desNo) & ".txt")
		ReDim ptCrv(0)
		ReDim strCrv(0)
		ReDim surfaces(0)
		' this is the code for the first four/Five patch at the AFT
		k = 0
		j = 0
		While UBound(surfaces) <= UBound(curvesInEachPatch)
			ptCrv(UBound(ptCrv)) = pointSet(k)
			ReDim Preserve ptCrv(UBound(ptCrv)+1)
			If UBound(ptCrv) = numOfPointsInCurve(n) Then
				ReDim Preserve ptCrv(UBound(ptCrv)-1)
				If firstCurve = False And numOfPointsInCurve(n) = (totalNoOfPtsOnEachCrv + 1) Then
					ReDim Preserve checkCurves(UBound(checkCurves)-1)
					checkCrvJoin = Rhino.JoinCurves(checkCurves)(0)
					checkCrvDivid = Rhino.DivideCurve(checkCrvJoin, totalNoOfPtsOnEachCrv)
					
					ptCrv_temp = getSegmentedPoints_v2(checkPoints, checkCrvDivid)
					
					strCrv_temp(0) = Rhino.AddInterpCurveEx(ptCrv_temp(0))
					strCrv_temp(1) = Rhino.AddInterpCurveEx(ptCrv_temp(1))
					strCrv_temp(2) = Rhino.AddInterpCurveEx(ptCrv_temp(2))
					strCrv_temp(3) = Rhino.AddInterpCurveEx(ptCrv_temp(3))
					
					strCrv(UBound(strCrv)) = Rhino.JoinCurves(strCrv_temp)(0) 'Rhino.AddInterpCurveEx(ptCrv)
					firstCurve = True
				Else
					strCrv(UBound(strCrv)) = Rhino.AddInterpCurveEx(ptCrv)
				End If
				ReDim Preserve strCrv(UBound(strCrv) + 1)
				ReDim ptCrv(0)
			End If
			k = k + 1
			
			If UBound(strCrv) = curvesInEachPatch(j) Then
				ReDim Preserve strCrv(UBound(strCrv)-1)
				If j = 0 Or j = 2 Or j = 3 Or j = 4 Then
					checkPoints(UBound(checkPoints)) = Rhino.CurveEndPoint(strCrv(UBound(strCrv)))
					'Rhino.SelectObject(Rhino.AddPoint(checkPoints(UBound(checkPoints))))
					checkCurves(UBound(checkCurves)) = Rhino.CopyObject(strCrv(UBound(strCrv)))
					ReDim Preserve checkPoints(UBound(checkPoints)+1)
					ReDim Preserve checkCurves(UBound(checkCurves)+1)
				End If 
				If j = 0 Then
					stern(0) = Rhino.CopyObject(strCrv(0))
					
				End If
				If j = 1 Then
					lastCrvOfPatch2 = Rhino.CopyObject(strCrv(UBound(strCrv)))
					stern(1) = Rhino.CopyObject(strCrv(0))
				End If
				If j = 2 Then
					ReDim temp(UBound(strCrv)+1)
					temp(0) = lastCrvOfPatch2
					For m = 0 To UBound(strCrv)
						temp(m + 1) = strCrv(m)
					Next
					strCrv = temp
				End If
				If j = 3 Then
					endPtForLoft = Rhino.CurveEndPoint(strCrv(0))
				End If
				If j = 4 Then
					ReDim temp_end(0)
					ReDim temp_start(0)
					temp_end(0) = endPtForLoft
					temp_start(0) = endPtForLoft
					ReverseCurveFromYAxis strCrv
					For m = 0 To UBound(strCrv)
						ReDim Preserve temp_end(UBound(temp_end)+1)
						ReDim Preserve temp_start(UBound(temp_start)+1)
						temp_end(m + 1) = Rhino.CurveEndPoint(strCrv(m))
						temp_start(m + 1) = Rhino.CurveStartPoint(strCrv(m))
					Next
					Rhino.AddInterpCurveEx temp_end
					surfaces(UBound(surfaces)) = Rhino.AddLoftSrf(array(Rhino.AddInterpCurveEx(temp_end), Rhino.AddInterpCurveEx(temp_start)), , , 3, 0)(0)
				Else
					surfaces(UBound(surfaces)) = Rhino.AddLoftSrf(strCrv, , , 3, 0)(0)
				End If
				
				ReDim Preserve surfaces(UBound(surfaces) + 1)
				ReDim strCrv(0)
				j = j + 1
				n = n + 1
			End If
			
			'If UBound(surfaces) < 5 Then
			'	numOfPointsInCurve = round(totalNoOfPtsOnEachCrv * 0.30) + 1
			'Else
			'	numOfPointsInCurve = totalNoOfPtsOnEachCrv + 1
			'End If
		Wend
		Dim s, s_m, trans
		s = Rhino.JoinCurves(stern, True)(0)
		s_m = Rhino.MirrorObject(s, Rhino.WorldZXPlane, True)
		
		trans = Rhino.AddLoftSrf(array(s, s_m), , , 3, 0)(0)
		ReDim Preserve surfaces(UBound(surfaces) - 1)
		
		Rhino.Command("SelCrv")
		Rhino.Command("Delete")
		
		Dim hull_half_1, hull_half_2, hull
		hull_half_1 = Rhino.JoinSurfaces(surfaces, True)

		hull_half_2 = Rhino.MirrorObject(hull_half_1, Rhino.WorldZXPlane, True)
		
		hull = Rhino.JoinSurfacesEx(array(hull_half_1, hull_half_2, trans), True)(0)
		
		' this is the code for the Middle and foward part
		Rhino.CapPlanarHoles hull
		Rhino.Command("_SelAll _Volume _Enter")
	Next
	
End Sub


'---------------------------------------------------------------
' Subroutine: ImportPoints
' Purpose:    Import points from a text file.
'---------------------------------------------------------------
Function ImportPoints(strFileName)
	Dim arrAllPoint()
	' Prompt the user for a file to import
	Dim strFilter
	strFilter = "Text File (*.txt)|*.txt|All Files (*.*)|*.*|"
	'	strFileName = Rhino.OpenFileName("Open Point File", strFilter)
	If IsNull(strFileName) Then Exit Function
 
	' The the file system object
	Dim objFSO, objFile
	Set objFSO = CreateObject("Scripting.FileSystemObject")
	' Try opening the text file
	On Error Resume Next
	Set objFile = objFSO.OpenTextFile(strFileName, 1)
	If Err Then
		MsgBox Err.Description
		Exit Function
	End If
 
	Rhino.EnableRedraw False
 
	' Read each line from the file
	Dim strLine, arrPoint, i
	i = 0
	Do While objFile.AtEndOfStream <> True
		strLine = objFile.ReadLine
		If Not IsNull(strLine) Then
			' Remove any double-quote characters
			strLine = Replace(strLine, Chr(34), , 1)
			' Convert the string to a 3D point
			arrPoint = Rhino.Str2Pt(strLine)
			' Add the point to Rhino
			If IsArray(arrPoint) Then
				ReDim Preserve arrAllPoint(i)
				' AddPoint will add a point object to Rhino
				'	Rhino.AddPoint arrPoint
				arrAllPoint(i) = arrPoint
				i = i + 1
			End If
		End If
	Loop
 
	Rhino.EnableRedraw True
	objFile.Close
	Set objFile = Nothing
	Set objFSO = Nothing
	
	ImportPoints = arrAllPoint
End Function

Function getSegmentedPoints_v2(arrCheckPoint, arrPoints)
	Dim segPoints(), i
	ReDim segPoints(3)
	segPoints(0) = FilterPointsByZ(arrPoints, arrCheckPoint(0))
	
	segPoints(1) = FilterPointsByY(arrPoints, arrCheckPoint(1))
	segPoints(1) = PointsBetweenCheckpoints(segPoints(1), arrCheckPoint(0), arrCheckPoint(1))
	
	segPoints(2) = FilterPointsByY(arrPoints, arrCheckPoint(2))
	segPoints(2) = PointsBetweenCheckpoints(segPoints(2), arrCheckPoint(1), arrCheckPoint(2))
	
	segPoints(3) = FilterPointsByY_less(arrPoints, arrCheckPoint(2))
	getSegmentedPoints_v2 = segPoints
End Function

Function getSegmentedPoints(arrPoints)
	Dim i, j
	Dim segPoints(), temp_segPoints()
	ReDim temp_segPoints(0)
	
	' For first curve whose points are from 0-18
	j = 1
	temp_segPoints(0) = arrPoints(0)
	For i = 1 To 17 ' if we do any chnage it only happen here 
		ReDim Preserve temp_segPoints(UBound(temp_segPoints)+1)
		temp_segPoints(j) = arrPoints(i)
		j = j + 1
	Next
	ReDim segPoints(0)
	segPoints(0) = temp_segPoints
	
	' For second curve whose points are from 18-70
	ReDim temp_segPoints(0)
	j = 0
	For i = 17 To 70' if we do any chnage it only happen here 
		temp_segPoints(j) = arrPoints(i)
		ReDim Preserve temp_segPoints(UBound(temp_segPoints)+1)
		j = j + 1
	Next	
	ReDim Preserve temp_segPoints(UBound(temp_segPoints)-1)
	ReDim Preserve segPoints(UBound(segPoints)+1)
	segPoints(UBound(segPoints)) = temp_segPoints
	
	
	' For second curve whose points are from 70-82
	ReDim temp_segPoints(0)
	j = 0
	For i = 70 To 99' if we do any chnage it only happen here 
		temp_segPoints(j) = arrPoints(i)
		ReDim Preserve temp_segPoints(UBound(temp_segPoints)+1)
		j = j + 1
	Next	
	ReDim Preserve temp_segPoints(UBound(temp_segPoints)-1)
	ReDim Preserve segPoints(UBound(segPoints)+1)
	segPoints(UBound(segPoints)) = temp_segPoints
	
	
	' For second curve whose points are from 82-100
	ReDim temp_segPoints(0)
	j = 0
	For i = 99 To 100' if we do any chnage it only happen here 
		temp_segPoints(j) = arrPoints(i)
		ReDim Preserve temp_segPoints(UBound(temp_segPoints)+1)
		j = j + 1
	Next	
	ReDim Preserve temp_segPoints(UBound(temp_segPoints)-1)
	ReDim Preserve segPoints(UBound(segPoints)+1)
	segPoints(UBound(segPoints)) = temp_segPoints
	
	getSegmentedPoints = segPoints
End Function

Function getSegmentedPoints_50(arrPoints)
	Dim i, j
	Dim segPoints(), temp_segPoints()
	ReDim temp_segPoints(0)
	
	' For first curve whose points are from 0-18
	j = 1
	temp_segPoints(0) = arrPoints(0)
	For i = 1 To 9 ' if we do any chnage it only happen here 
		ReDim Preserve temp_segPoints(UBound(temp_segPoints)+1)
		temp_segPoints(j) = arrPoints(i)
		j = j + 1
	Next
	ReDim segPoints(0)
	segPoints(0) = temp_segPoints
	
	' For second curve whose points are from 18-70
	ReDim temp_segPoints(0)
	j = 0
	For i = 9 To 37' if we do any chnage it only happen here 
		temp_segPoints(j) = arrPoints(i)
		ReDim Preserve temp_segPoints(UBound(temp_segPoints)+1)
		j = j + 1
	Next	
	ReDim Preserve temp_segPoints(UBound(temp_segPoints)-1)
	ReDim Preserve segPoints(UBound(segPoints)+1)
	segPoints(UBound(segPoints)) = temp_segPoints
	
	
	' For second curve whose points are from 70-82
	ReDim temp_segPoints(0)
	j = 0
	For i = 37 To 49' if we do any chnage it only happen here 
		temp_segPoints(j) = arrPoints(i)
		ReDim Preserve temp_segPoints(UBound(temp_segPoints)+1)
		j = j + 1
	Next	
	ReDim Preserve temp_segPoints(UBound(temp_segPoints)-1)
	ReDim Preserve segPoints(UBound(segPoints)+1)
	segPoints(UBound(segPoints)) = temp_segPoints
	
	
	' For second curve whose points are from 82-100
	ReDim temp_segPoints(0)
	j = 0
	For i = 49 To 50' if we do any chnage it only happen here 
		temp_segPoints(j) = arrPoints(i)
		ReDim Preserve temp_segPoints(UBound(temp_segPoints)+1)
		j = j + 1
	Next	
	ReDim Preserve temp_segPoints(UBound(temp_segPoints)-1)
	ReDim Preserve segPoints(UBound(segPoints)+1)
	segPoints(UBound(segPoints)) = temp_segPoints
	
	getSegmentedPoints_50 = segPoints
End Function

Function FilterPointsByZ(arrPoints, ptCheckpoint)
	Dim i, arrFiltered(), count, zThreshold, foundMatch
    
	' Z coordinate of the checkpoint
	zThreshold = ptCheckpoint(2)
    
	count = -1
	foundMatch = False
	For i = 0 To UBound(arrPoints)
		If arrPoints(i)(2) = zThreshold Then
			foundMatch = True
		End If
        
		If arrPoints(i)(2) > zThreshold Then
			count = count + 1
			ReDim Preserve arrFiltered(count)
			arrFiltered(count) = arrPoints(i)
		End If
	Next

	' If no point with matching Z coordinate was found, add the checkpoint
	If Not foundMatch Then
		count = count + 1
		ReDim Preserve arrFiltered(count)
		arrFiltered(count) = ptCheckpoint
	End If
    
	FilterPointsByZ = arrFiltered
End Function



Function FilterPointsByY_less(arrPoints, ptCheckpoint)
	Dim i, arrFiltered(), count, zThreshold, foundMatch
    
	' Z coordinate of the checkpoint
	zThreshold = ptCheckpoint(1)
    
	count = -1
	foundMatch = False
	For i = 0 To UBound(arrPoints)
		If arrPoints(i)(1) = zThreshold Then
			foundMatch = True
		End If
        
		If arrPoints(i)(1) < zThreshold Then
			count = count + 1
			ReDim Preserve arrFiltered(count)
			arrFiltered(count) = arrPoints(i)
		End If
	Next

	' If no point with matching Z coordinate was found, add the checkpoint
	If Not foundMatch Then
		count = count + 1
		ReDim Preserve arrFiltered(count)
		For i = count To 1 Step -1
			arrFiltered(i) = arrFiltered(i - 1)
		Next
		arrFiltered(0) = ptCheckpoint
	End If
    
	FilterPointsByY_less = arrFiltered
End Function

Function FilterPointsByY(arrPoints, ptCheckpoint)
	Dim i, arrFiltered(), count, zThreshold
    
	' Z coordinate of the checkpoint
	zThreshold = ptCheckpoint(1)
    
	count = -1
	For i = 0 To UBound(arrPoints)
		If arrPoints(i)(1) >= zThreshold Then
			count = count + 1
			ReDim Preserve arrFiltered(count)
			arrFiltered(count) = arrPoints(i)
		End If
	Next
    
	FilterPointsByY = arrFiltered
End Function

Function PointsBetweenCheckpoints(arrPoints, ptCheckpoint1, ptCheckpoint2)
	Dim i, arrFiltered(), count, zMin, zMax, foundMatch1, foundMatch2
    
	' Determine the Z range based on the two checkpoints
	If ptCheckpoint1(2) < ptCheckpoint2(2) Then
		zMin = ptCheckpoint1(2)
		zMax = ptCheckpoint2(2)
	Else
		zMin = ptCheckpoint2(2)
		zMax = ptCheckpoint1(2)
	End If
    
	count = -1
	foundMatch1 = False
	foundMatch2 = False
    
	For i = 0 To UBound(arrPoints)
		If arrPoints(i)(2) = ptCheckpoint1(2) Then
			foundMatch1 = True
		ElseIf arrPoints(i)(2) = ptCheckpoint2(2) Then
			foundMatch2 = True
		End If

		If arrPoints(i)(2) > zMin And arrPoints(i)(2) < zMax Then
			count = count + 1
			ReDim Preserve arrFiltered(count)
			arrFiltered(count) = arrPoints(i)
		End If
	Next

	' If no point with Z coordinate matching ptCheckpoint1 was found, add it to the beginning
	If Not foundMatch1 Then
		count = count + 1
		ReDim Preserve arrFiltered(count)
		For i = count To 1 Step -1
			arrFiltered(i) = arrFiltered(i - 1)
		Next
		arrFiltered(0) = ptCheckpoint1
	End If

	' If no point with Z coordinate matching ptCheckpoint2 was found, add it to the end
	If Not foundMatch2 Then
		count = count + 1
		ReDim Preserve arrFiltered(count)
		arrFiltered(count) = ptCheckpoint2
	End If
    
	PointsBetweenCheckpoints = arrFiltered
End Function

Function ReverseCurveFromYAxis(arrCurves)
	Dim i, ptStart, ptEnd
    
	For i = 0 To UBound(arrCurves)
		ptStart = Rhino.CurveStartPoint(arrCurves(i))
		ptEnd = Rhino.CurveEndPoint(arrCurves(i))
        
		' Check if the curve is facing upwards based on Z-values
		If ptStart(1) < ptEnd(1) Then 
			' If the curve is facing upwards, reverse the curve
			Rhino.ReverseCurve arrCurves(i)
		End If
	Next
End Function
